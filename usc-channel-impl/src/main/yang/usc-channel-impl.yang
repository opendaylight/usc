module usc-channel-impl {

    yang-version 1;
    
    namespace "urn:opendaylight:params:xml:ns:yang:usc:channel:impl";
    
    prefix "usc-channel-impl";

    import config { prefix config; revision-date 2013-04-05; }
    import opendaylight-md-sal-binding { prefix mdsal; revision-date 2013-10-28;}
    import ietf-inet-types {prefix inet; revision-date 2013-07-15;}
    import usc-channel { prefix usc-channel; revision-date 2015-01-01;}

    description "This module defines the model for USC channels.";

    revision "2015-01-01" {
        description "Initial revision of USC channels.";
    }

    identity usc-channel-impl {
        base config:module-type;
        config:java-name-prefix UscChannelImpl;
    }   

    augment "/config:modules/config:module/config:configuration" {
        case usc-channel-impl {
            when "/config:modules/config:module/config:type = 'usc-channel-impl'";
            container broker {
                uses config:service-ref {
                    refine type {
                        mandatory true;
                        config:required-identity mdsal:binding-broker-osgi-registry;
                    }
                }
            }
            container data-broker {
                uses config:service-ref {
                    refine type {
                        mandatory false;
                        config:required-identity mdsal:binding-async-data-broker;
                    }
                }
            }
        }
    }
    
}
