module usc-impl {
    yang-version 1;
    namespace "urn:opendaylight:params:xml:ns:yang:usc:impl";
    prefix "usc-impl";

    import config { prefix config; revision-date 2013-04-05; }
    import opendaylight-md-sal-binding { prefix mdsal; revision-date 2013-10-28;}
    import usc { prefix usc; revision-date 2015-01-01;}
    import ietf-inet-types {prefix inet; revision-date 2010-09-24;}

    description
        "Service definition for usc project";

    revision "2015-01-01" {
        description
            "Initial revision";
    }

    identity usc-impl {
        base config:module-type;
        config:java-name-prefix UscImpl;
    }   
  
    container usc-root{
		uses usc:topologies;
		description
			"the USC related whole topology.";
    }
    
    augment "/config:modules/config:module/config:configuration" {
        case usc-impl {
            when "/config:modules/config:module/config:type = 'usc-impl'";

            container broker {
                uses config:service-ref {
                    refine type {
                        mandatory true;
                        config:required-identity mdsal:binding-broker-osgi-registry;
                    }
                }
            }
            container data-broker {
                uses config:service-ref {
                    refine type {
                        mandatory false;
                        config:required-identity mdsal:binding-async-data-broker;
                    }
                }
            }
        }
    }
}
