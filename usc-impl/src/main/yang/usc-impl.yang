module usc-impl {
    yang-version 1;
    namespace "urn:opendaylight:params:xml:ns:yang:usc:impl";
    prefix "usc-impl";

    import config { prefix config; revision-date 2013-04-05; }
    import opendaylight-md-sal-binding { prefix mdsal; revision-date 2013-10-28;}
    import usc { prefix usc; revision-date 2015-01-01;}
    import ietf-inet-types {prefix inet; revision-date 2010-09-24;}

    description
        "Service definition for usc project";

    revision "2015-01-01" {
        description
            "Initial revision";
    }

    identity usc-impl {
        base config:module-type;
        config:java-name-prefix UscImpl;
    }   
  
    container usc-root{
		uses usc:usc-topology;
		description
			"the USC related whole topology.";
    }
    
    augment "/config:modules/config:module/config:configuration" {
        case usc-impl {
            when "/config:modules/config:module/config:type = 'usc-impl'";
            leaf usc-plugin-port {
                type inet:port-number;
                default 1069;
                description "the port number of the USC Plugin";
            }
            leaf usc-agent-port {
                type inet:port-number;
                default 1068;
                description "the port number of the USC agent";
            }
            leaf max-error-number {
                type int32;
                default 100;
                description "the max number of errors of each session or USC channel";
            }
            leaf max-thread-number {
                type int32;
                default 100;
                description "the max thread pool size for the thread pool of asynchronous event handler ";
            }
            leaf certificates-root {
                type string;
                default "src/main/certificates";
                description "the root directory of all of security certificates";
            }

            container broker {
                uses config:service-ref {
                    refine type {
                        mandatory true;
                        config:required-identity mdsal:binding-broker-osgi-registry;
                    }
                }
            }
            
            container rpc-registry {
                uses config:service-ref {
                    refine type {
                        mandatory true;
                        config:required-identity mdsal:binding-rpc-registry;
                    }
                }
            }

            container notification-service {
                uses config:service-ref {
                    refine type {
                        mandatory true;
                        config:required-identity mdsal:binding-notification-service;
                    }
                }
            }

            container data-broker {
                uses config:service-ref {
                    refine type {
                        mandatory false;
                        config:required-identity mdsal:binding-async-data-broker;
                    }
                }
            }
        }
    }
}
