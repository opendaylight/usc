module usc {
    
    yang-version 1;
    
    namespace "urn:opendaylight:params:xml:ns:yang:usc";
    
    prefix "usc";

    description "This module defines a model for unified secure channels.";

    revision "2015-01-01" {
        description "Initial revision of usc model.";
    }

    typedef topology-id {
        type string;
        description
            "An identifier for a topology.";
    }
    
    typedef alarm-id {
        type string;
        description
            "An identifier for an error in a topology.";
    }

    typedef node-id {
        type string;
        description
            "An identifier for a node in a topology.";
    }

    typedef link-id {
        type string;
        description
            "An identifier for a link in a topology.";
    }
    
    typedef session-id {
        type string;
        description
            "An identifier for a session in a link.";
    }
    
    typedef terminal-point-id {
        type string;
        description
            "An identifier for a terminal-point in a session.";
    }
    
    grouping alarm-attributes {
        
        description
            "The attributes of an alarm message.";

        leaf alarm-id {
            type alarm-id;
            description
                "The identifier of an alarm message.";
        }
        
        leaf alarm-code {
            type string;
            description
                "The code of an alarm message.";
        }
        
        leaf alarm-message {
            type string;
            description
                "The text of an alarm message.";
        }
        
    }

    grouping node-attributes {
        
        description
            "The attributes of a node.";

        leaf node-id {
            type node-id;
            description
                "The identifier of a node in the topology.";
        }
        
        leaf node-type {
            type string;
            description
                "The identifier of a node type.";
        }
        
    }

    grouping link-attributes {
        
        description
            "The attributes of a link .";
            
        leaf link-id {
            type link-id;
            description
                "The identifier of a link in the topology.";
        }
        
        leaf link-type {
            type string;
            description
                "The identifier of a link type.";
        }
        
        container source {
                
            description
                "The logical source of a particular link.";
                
            leaf source-node {
                type node-id;
                description
                    "Source node identifier.";
            }
            
        }
        
        container destination {
        
            description
                "The logical destination of a particular link.";
                
            leaf dest-node {
                type node-id;
                description
                    "Destination node identifier.";
            }

        }
        
        leaf bytes-in {
            type uint32;
            description
                "Volume of bytes in.";
        }
        
        leaf bytes-out {
            type uint32;
            description
                "Volume of bytes out.";
        }
        
        leaf call-home {
            type string;
            description
                "Call home attribute.";
        }
        
        leaf alarms {
            type uint32;
            description
                "Number of errors.";
        }
        
        list alarm {
                
            description 
                "The list of alarms for the link.";
                
            key "alarm-id";
            
            uses alarm-attributes;
            
        }
        
        leaf sessions {
            type uint32;
            description
                "Number of sessions.";
        }
        
        list session {
                
            description
                "The list of sessions defined for the link.";
                
            key "session-id";

            uses session-attributes;

        }
        
    }
    
    grouping session-attributes {
        
        description
            "The attributes of a session.";
            
        leaf session-id {
            type session-id;
            description
                "The identifier of a session in an USC Channel.";
        }    
        
        container terminal-point {
                
            description
                "The logical terminal point of a particular session.";
            
            uses terminal-point-attributes;
            
        }
        
        leaf bytes-in {
            type uint32;
            description
                "Volume of bytes in.";
        }
        
        leaf bytes-out {
            type uint32;
            description
                "Volume of bytes out.";
        }
        
        leaf alarms {
            type uint32;
            description
                "Number of alarms.";
        }
        
        list alarm {
                
            description 
                "The list of alarms for the session.";
                
            key "alarm-id";
            
            uses alarm-attributes;
            
        }
        
    }
    
    grouping terminal-point-attributes {
        
        description
            "The attributes of a terminal point.";
            
        leaf terminal-point-id {
            type terminal-point-id;
            description
                "The identifier of a terminal point in the session.";
        }      
    }

    grouping topologies {
    
        description
            "A model of the unified secure channel topology.";
                    
        list topology {
        
            description 
                "A model of an abstract topology.";
                
            key "topology-id";
    
            leaf topology-id {
                type topology-id;
                description
                    "An identifier for a topology.";
            }

            list node {
                
                description 
                    "The list of nodes defined for the topology.";
                    
                key "node-id";
                
                uses node-attributes;
                
            }

            list link {
            
                description
                    "The list of links defined for the topology.";
                    
                key "link-id";
            
                uses link-attributes;

            }
            
        }
        
    }

    rpc usc-topology {
    
        description
            "View model of the unified secure channel topology. ";
                            
        input {
            
            leaf topology-id {
                type topology-id;
                description
                    "An identifier for a topology.";
            }
        
        }
        
        output {

            container usc-topology {
                uses topologies;
                description
                    "A model of the unified secure channel topology.";
            }
            
        }
        
    }  
}
