module usc-test {

    yang-version 1;

    namespace "urn:opendaylight:params:xml:ns:yang:usc:test";

    prefix "usc-test";

    description "This module defines the model for USC Tests.";

    revision "2015-01-01" {
        description "Initial revision of USC Tests.";
    }

    rpc add-channel {

        description
            "Add a channel to the USC topology.";
             
        input {

            container channel {

            	description
                    "The channel to be added.";

            	leaf hostname{
            		type string;
            		description 
            		            "The ip address of target Netconf device.";
            	}
            	leaf port{
            		type int16;
            		description 
            		            "The port of target Netconf device.";
            	}
            	
            	leaf remote{
            		type boolean;
            		description 
            		            "true for remote,false for local.";
            	}
            }

        }
        output{
                leaf result{
            		type string;
            		description 
            		            "The result message of rest request.";
            	}
        }

    }
    rpc remove-channel {

        description
            "remove a channel to the USC topology.";
             
        input {

            container channel {

            	description
                    "The channel to be added.";

            	leaf hostname{
            		type string;
            		description 
            		            "The ip address of target Netconf device.";
            	}
            	leaf port{
            		type int16;
            		description 
            		            "The port of target Netconf device.";
            	}        	
            }
        }
        output{
                leaf result{
            		type string;
            		description 
            		            "The result message of rest request.";
            	}
        }

    }
   
    rpc netconf-request {

        description
            "send a netconf request to a USC Channel.";
             
        input {

            container channel {

            	description
                    "The channel to be added.";

            	leaf hostname{
            		type string;
            		description 
            		            "The ip address of target Netconf device.";
            	}
            	leaf port{
            		type int16;
            		description 
            		            "The port of target Netconf device.";
            	}        	
            	leaf content{
            		type string;
            		description 
            		            "The content of Netconf request, real netconf xml content.";
            	}
            }
        }
        output{
                leaf result{
            		type string;
            		description 
            		            "The result message of rest request.";
            	}
        }

    }
    
}
